# SRS

# Specification: SRS

## 1: Braking

### 2
The controller shall apply the brakes within 50 ms.
Measured at the wheel.
- Verification Method: Test
- Status: Approved
- Jira Issue: BRK-101, BRK-102
- satisfies -> 1

### 3
The brake command shall be retried
at most twice.
- Verification Method: Analysis
- Status: Draft
- satisfies -> 2

### 4
Brake lights shall turn on with the brakes.
- refers to -> 2
